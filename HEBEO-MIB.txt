HEBEO-MIB DEFINITIONS ::= BEGIN
IMPORTS
OBJECT-TYPE, NOTIFICATION-TYPE, MODULE-IDENTITY,
Integer32, Opaque, enterprises, Counter32
FROM SNMPv2-SMI
TEXTUAL-CONVENTION, DisplayString, TruthValue
FROM SNMPv2-TC;

Hebeo MODULE-IDENTITY
LAST-UPDATED "201411111908Z"
ORGANIZATION "Hebeo http://www.hebeo.org/"
CONTACT-INFO
"email: damien@hebeo.org"
DESCRIPTION
"HEBEO MIB"
::= { enterprises 44687 }

Admin OBJECT IDENTIFIER ::= { Hebeo 1 }
Freebox OBJECT IDENTIFIER ::= { Hebeo 2 }

Memcache OBJECT IDENTIFIER ::= { Admin 1 }
Netstat OBJECT IDENTIFIER ::= { Admin 2 }
InodeCount OBJECT IDENTIFIER ::= { Admin 3 }
InodeByPart OBJECT IDENTIFIER ::= { Admin 4 }
Threads OBJECT IDENTIFIER ::= { Admin 5 }
Entropy OBJECT IDENTIFIER ::= { Admin 6 }
Interrupts OBJECT IDENTIFIER ::= { Admin 7 }
Irqstats OBJECT IDENTIFIER ::= { Admin 8 }
IOStats OBJECT IDENTIFIER ::= { Admin 9 }
ForkRate OBJECT IDENTIFIER ::= { Admin 10 }
ProcessPriority OBJECT IDENTIFIER ::= { Admin 11 }
Filetable OBJECT IDENTIFIER ::= { Admin 12 }
Apache2Stats OBJECT IDENTIFIER ::= { Admin 13 }
Apache2Requests OBJECT IDENTIFIER ::= { Admin 14 }

FbxAPIVersion OBJECT IDENTIFIER ::= { Freebox 1 }
FbxLanHosts OBJECT IDENTIFIER ::= { Freebox 2 }
FbxFreeplugs OBJECT IDENTIFIER ::= { Freebox 3 }
FbxUPNP OBJECT IDENTIFIER ::= { Freebox 4 }
FbxSystem OBJECT IDENTIFIER ::= { Freebox 20 }
FbxConnection OBJECT IDENTIFIER ::= { Freebox 21 }
FbxLan OBJECT IDENTIFIER ::= { Freebox 22 }

NetstatEstablished ::= { Netstat 1 }
NetstatSynSent ::= { Netstat 2 }
NetstatSynRecv ::= { Netstat 3 }
NetstatFinWait1 ::= { Netstat 4 }
NetstatFinWait2 ::= { Netstat 5 }
NetstatTimeWait ::= { Netstat 6 }
NetstatClose ::= { Netstat 7 }
NetstatCloseWait ::= { Netstat 8 }
NetstatLastAck ::= { Netstat 9 }
NetstatListen ::= { Netstat 10 }
NetstatClosing ::= { Netstat 11 }
NetstatUnknown ::= { Netstat 12 }

Apache2RequestsWaiting OBJECT IDENTIFIER ::= { Apache2Requests 1 }
Apache2RequestsStarting OBJECT IDENTIFIER ::= { Apache2Requests 2 }
Apache2RequestsReading OBJECT IDENTIFIER ::= { Apache2Requests 3 }
Apache2RequestsReply OBJECT IDENTIFIER ::= { Apache2Requests 4 }
Apache2RequestsKeepalive OBJECT IDENTIFIER ::= { Apache2Requests 5 }
Apache2RequestsDnsLookup OBJECT IDENTIFIER ::= { Apache2Requests 6 }

FbxLanHostsTotal OBJECT IDENTIFIER ::= { FbxLanHosts 1 }
FbxLanHostsOnline OBJECT IDENTIFIER ::= { FbxLanHosts 2 }

FbxSystemMac OBJECT IDENTIFIER ::= { FbxSystem 1 }
FbxSystemBoardName OBJECT IDENTIFIER ::= { FbxSystem 2 }
FbxSystemFanRpm OBJECT IDENTIFIER ::= { FbxSystem 3 }
FbxSystemTempSW OBJECT IDENTIFIER ::= { FbxSystem 4 }
FbxSystemUptime OBJECT IDENTIFIER ::= { FbxSystem 5 }
FbxSystemUptimeVal OBJECT IDENTIFIER ::= { FbxSystem 6 }
FbxSystemTempCpuB OBJECT IDENTIFIER ::= { FbxSystem 7 }
FbxSystemTempCpuM OBJECT IDENTIFIER ::= { FbxSystem 8 }
FbxSystemSerial OBJECT IDENTIFIER ::= { FbxSystem 9 }
FbxSystemFirmwareVersion OBJECT IDENTIFIER ::= { FbxSystem 10 }

END
